module spad {
  yang-version 1.1;
  namespace "http://spad.fluffy.im/module";
  prefix "spad";

  import ietf-inet-types {
         prefix "yang";
  }
       
  organization
    "IETF";
  contact
    "fluffy@iii.ca";
  description
    "The module for entities 
     implementing the SPAD";

  revision 2017-10-02 {
    description
      "Initial revision.";
  }

  container spad {
    leaf domain {
      type yang:domain-name;
      mandatory true;
    }
    leaf validTill {
      type string;
    }
    list services {
      key "name";
      leaf name {
        type string;
      }
      
      list flows {
        key protocol;
        leaf port {
          type yang:port-number;
        }
        leaf protocol {
          type yang:domain-name;
        }
        leaf name {
          type string;
        }
        leaf qos {
          type yang:dscp;
        }
        leaf-list ips {
          //type yang:ip-prefix;
          type yang:ip-address;
        }
      }
    }
  }
}
