module ietf-spad {
  yang-version 1.1;
  namespace "urn:ietf:params:xml:ns:yang:ietf-spad";
  prefix "spad";

  import ietf-inet-types {
         prefix "inet";
  }
       
  import ietf-yang-types {
         prefix "yang";
  }
       
organization
    "IETF";
  contact
    "fluffy@iii.ca";
  description
    "The module for entities 
     implementing the SPAD";

  revision 2017-10-02 {
    description
      "Initial revision.";
  }

  container spad {
    leaf domain {
      type inet:domain-name;
      mandatory true;
      description "Domain that produced this SPAD file";
    }
    leaf validTill {
      type yang:date-and-time;
    }
    list services {
      key "name";
      leaf name {
        type string;
      }
      
      list flows {
        key protocol;
        leaf port {
          type inet:port-number;
        }
        leaf protocol {
          type string;
        }
        leaf name {
          type inet:domain-name;
        }
        leaf qos {
          type inet:dscp;
        }
        leaf-list ips {
          //type inet:ip-prefix;
          type inet:ip-address;
        }
      }
    }
  }
}
